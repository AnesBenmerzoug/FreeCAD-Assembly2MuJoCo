#!/usr/bin/env python
# -*- coding: utf-8 -*-

"""
FreeCAD Macro for exporting a FreeCAD assembly made with the builtin Assembly Workbench
to MuJoCo.
"""

__Name__ = "Assembly Export To MuJoCo"
__Comment__ = (
    "Export selected assembly to STL and creates an MJCF (XML) for use in MuJoCo"
)
__Author__ = "Anes Benmerzoug"
__Version__ = "0.1.0"
__Date__ = "2025-05-04"
__License__ = "LGPL-2.1-only"
__Web__ = "https://github.com/AnesBenmerzoug/FreeCAD-Macro-Assembly-Export-to-MuJoCo"
__Wiki__ = ""
__Icon__ = "AssemblyExportToMuJoCo.svg"
__Help__ = "Create your assembly using the builtin Assembly Workbench. Then select and run the macro to export its parts as meshes and create an MJCF file for MuJoCo."
__Status__ = "Beta"
__Requires__ = "FreeCAD >= 1.0"
__Communication__ = (
    "https://github.com/AnesBenmerzoug/FreeCAD-Macro-Assembly-Export-to-MuJoCo/issues"
)
__Files__ = "AssemblyExportToMuJoCo.svg"

import math
import os
import xml.etree.ElementTree as ET
from pathlib import Path
from typing import Any, Literal, TypedDict

import FreeCAD as App
import FreeCADGui as Gui
import MeshPart
import UtilsAssembly
from PySide import QtGui, QtWidgets

####################################################################
# Constants
####################################################################

MACRO_NAME = "AssemblyExportToMuJoCo"

MUJOCO_JOINT_TYPE = Literal["hinge", "slide", "ball", "free"]

DEFAULT_LINEAR_DEFLECTION: float = 0.5
DEFAULT_ANGULAR_DEFLECTION: float = 4.0
DEFAULT_MJCF_TIMESTEP: float = 0.002
DEFAULT_MJCF_DAMPING: float = 10.0
DEFAULT_MJCF_ARMATURE: float = 1.0
DEFAULT_MJCF_INTEGRATOR: Literal["Euler", "implicit", "implicitfast", "RK4"] = (
    "implicitfast"
)
DEFAULT_MJCF_SOLVER: Literal["PGS", "CG", "Newton"] = "Newton"

JOINT_TYPE_MAPPING: dict[str, MUJOCO_JOINT_TYPE] = {
    "Revolute": "hinge",
    "Prismatic": "slide",
    "Cylindrical": "hinge",
    "Ball": "ball",
    "Planar": "free",
}

# Assign weights to prioritize which joints to keep in the tree
# Higher weight are more likely to be excluded from tree
# Base weight by joint type
JOINT_TYPE_WEIGHTS = {
    "Fixed": 10.0,
    "Revolute": 1.0,
    "Prismatic": 2.0,
    "Cylindrical": 3.0,
    "Ball": 5.0,
    "Planar": 8.0,
}


####################################################################
# Utilities
####################################################################


def log_message(
    message: str,
    *,
    level: Literal["info", "warning", "error"] = "info",
) -> None:
    formatted_message = MACRO_NAME + ": " + message + "\n"
    if level == "info":
        App.Console.PrintMessage(formatted_message)
    elif level == "warning":
        App.Console.PrintWarning(formatted_message)
    elif level == "error":
        App.Console.PrintError(formatted_message)
    else:
        raise ValueError(f"Unrecognized log level '{level}'")


class JointAttributes(TypedDict):
    type: MUJOCO_JOINT_TYPE


class MaterialProperties(TypedDict):
    CardName: str
    AuthorAndLicense: str
    Author: str
    License: str
    Name: str
    Description: str
    ReferenceSource: str
    SourceURL: str
    AmbientColor: str  # e.g. '(0.8984, 0.7305, 0.3906, 1.0)'
    DiffuseColor: str  # e.g. '(0.8984, 0.7305, 0.3906, 1.0)'
    EmissiveColor: str  # e.g. '(0.8984, 0.7305, 0.3906, 1.0)'
    Shininess: str  # e.g. '0.95'
    SpecularColor: str  # e.g. '(0.8984, 0.7305, 0.3906, 1.0)'
    Transparency: str  # e.g. '0'


class AppearanceDict(TypedDict):
    name: str
    rgba: str
    shininess: str


####################################################################
# Assembly Graph Classes
####################################################################


class GraphNode:
    def __init__(
        self,
        part: App.DocumentObject,
    ) -> None:
        self.part = part

    def get_body_position_and_orientation(self) -> tuple[str, str]:
        """Get position and orientation for FreeCAD part in MuJoCo."""
        pos = "0 0 0"
        quat = "1.0 0.0 0.0 0.0"

        log_message(f"Part: Name={self.part.Name}, Pos={pos}, Quat={quat}")
        return pos, quat

    def get_body_material(
        self,
    ) -> MaterialProperties:
        material_properties: MaterialProperties = self.part.ShapeMaterial.Properties
        return material_properties

    def get_body_appearance(
        self,
    ) -> AppearanceDict:
        name = self.part.Name
        rgb = self.part.ViewObject.ShapeAppearance[0].DiffuseColor[:3]
        rgba = rgb + (1.0,)
        rgba = " ".join(str(x) for x in rgba)
        shininess = str(self.part.ViewObject.ShapeAppearance[0].Shininess)
        appearance_dict = AppearanceDict(name=name, rgba=rgba, shininess=shininess)
        return appearance_dict

    def __repr__(self) -> str:
        return f"<AssemblyGraphNode part={self.part.Name}>"

    def __hash__(self):
        return hash(repr(self))

    def __eq__(self, other: "GraphNode") -> bool:
        return self.part.Name == other.part.Name


class GraphEdge:
    def __init__(
        self,
        joint: App.DocumentObject,
        *,
        parent_node: GraphNode,
        child_node: GraphNode,
    ) -> None:
        self.joint = joint
        self.parent_node = parent_node
        self.child_node = child_node
        self.weight = self.compute_weight(self.joint)

    @staticmethod
    def compute_weight(joint) -> float:
        # Assign weights to prioritize which joints to keep in the tree
        # Higher weight are more likely to be excluded from tree
        weight = JOINT_TYPE_WEIGHTS.get(joint.JointType, 20.0)
        return weight

    def get_mujoco_joint_type(self) -> MUJOCO_JOINT_TYPE | None:
        mujoco_joint_type = JOINT_TYPE_MAPPING.get(self.joint.JointType)
        return mujoco_joint_type

    def get_joint_position_and_axis(self) -> tuple[str, str]:
        """Extract joint position and axis from FreeCAD joint"""
        assembly = self.parent_node.part.Parents[0][0]
        if assembly.Type != "Assembly":
            raise RuntimeError(
                f"{MACRO_NAME}: Unexpected error trying to get root assembly from part"
            )

        # Get global placement of joint
        global_plc = UtilsAssembly.getJcsGlobalPlc(
            self.joint.Placement1, self.joint.Reference1
        )

        if self.joint.JointType == "Revolute":
            pos_vector = global_plc.Base
            # For a Revolute joint, the Z-axis of the placement is the rotation axis
            # Transform the Z-axis (0,0,1) by the rotation part of the placement
            axis_vector = global_plc.Rotation.multVec(App.Vector(0, 0, 1))
            # axis_vector = UtilsAssembly.round_vector(axis_vector)

        else:
            raise NotImplementedError(
                f"Getting joint axis not implemented for joint type: {self.joint.JointType}"
            )

        # Convert mm to m
        pos = f"{pos_vector[0] / 1000} {pos_vector[1] / 1000} {pos_vector[2] / 1000}"
        axis = f"{axis_vector[0]} {axis_vector[1]} {axis_vector[2]}"

        log_message(f"Joint: Name={self.joint.Name}, Pos={pos}, Axis={axis}")
        return pos, axis

    def get_joint_range(self) -> str | None:
        """Extract joint range from a FreeCAD joint limits, if there are any."""
        limits = {"lower": None, "upper": None}

        # Try to get limits from joint
        if self.joint.EnableAngleMin:
            # Convert degrees to radian
            limits["lower"] = self.joint.AngleMin * math.pi / 180
        elif self.joint.EnableLengthMin:
            limits["lower"] = self.joint.LengthMin

        if self.joint.EnableAngleMax:
            limits["upper"] = self.joint.AngleMax * math.pi / 180
        elif self.joint.EnableLengthMax:
            limits["upper"] = self.joint.LengthMax

        # Calculate range if both limits are defined
        range: str | None = None
        if limits["lower"] is not None and limits["upper"] is not None:
            range = f"{limits['lower']} {limits['upper']}"

        return range

    def __eq__(self, other: "GraphEdge") -> bool:
        return self.joint == other.joint

    def __repr__(self) -> str:
        return f"<AssemblyGraphEdge joint={self.joint.JointType} weight={self.weight}>"

    def __hash__(self):
        return hash((self.joint.Name, self.joint.JointType))


class Graph:
    def __init__(self, *, is_directed: bool = False) -> None:
        self.is_directed = is_directed
        self.adjacency_list: dict[GraphNode, dict[GraphNode, GraphEdge]] = {}

    @classmethod
    def from_assembly(cls, assembly: App.DocumentObject) -> None:
        """Construct graph from FreeCAD assembly"""
        graph = cls()
        joint_group = UtilsAssembly.getJointGroup(assembly)
        for joint in joint_group.Group:
            # Grounded Joint will be set as the root of the graph
            if hasattr(joint, "ObjectToGround"):
                graph.add_node(joint.ObjectToGround)
            else:
                part1 = UtilsAssembly.getMovingPart(assembly, joint.Reference1)
                part2 = UtilsAssembly.getMovingPart(assembly, joint.Reference2)
                graph.add_edge(part1, part2, joint)
        return graph

    def add_node(self, part: App.DocumentObject) -> GraphNode:
        node = GraphNode(part)
        if node not in self.adjacency_list:
            self.adjacency_list[node] = {}
        return node

    def add_edge(
        self,
        part1: App.DocumentObject,
        part2: App.DocumentObject,
        joint: App.DocumentObject,
    ) -> None:
        node1 = self.add_node(part1)
        node2 = self.add_node(part2)
        edge = GraphEdge(joint, parent_node=node1, child_node=node2)
        self.adjacency_list[node1][node2] = edge
        if not self.is_directed:
            # Since undirected, add both directions
            self.adjacency_list[node2][node1] = edge

    def get_nodes(self) -> list[GraphNode]:
        """Return a list of all unique nodes."""
        return list(self.adjacency_list.keys())

    def get_neighbors(self, node: GraphNode) -> list[GraphNode]:
        return list(self.adjacency_list.get(node, []))

    def get_edge(self, u: GraphNode, v: GraphNode) -> GraphEdge | None:
        return self.adjacency_list.get(u, {}).get(v, None)

    def get_edges(
        self,
    ) -> list[tuple[GraphNode, GraphNode, dict[str, GraphEdge | Any]]]:
        """Return a list of all unique edges as (u, v, edge)."""
        seen: set[tuple[GraphNode, GraphNode]] = set()
        edge_list = []
        for u in self.adjacency_list:
            for v in self.adjacency_list[u]:
                if self.is_directed:
                    edge_key = (u, v)
                else:
                    edge_key = tuple(sorted((u, v), key=lambda x: x.part.Name))
                if edge_key not in seen:
                    edge = self.get_edge(edge_key[0], edge_key[1])
                    if edge is not None:
                        edge_list.append((edge_key[0], edge_key[1], edge))
                        seen.add(edge_key)
        return edge_list


####################################################################
# Minimum Spanning Tree
####################################################################


class UnionFind:
    def __init__(self, graph: Graph) -> None:
        # Initialize disjoint set for Kruskal's algorithm
        self.parent: dict[GraphNode, GraphNode] = {
            node: node for node in graph.get_nodes()
        }
        self.rank: dict[GraphNode, int] = {node: 0 for node in graph.get_nodes()}

    def find_root(self, node: GraphNode) -> GraphNode:
        if self.parent[node] != node:
            # Path compression
            self.parent[node] = self.find_root(self.parent[node])
        return self.parent[node]

    def union(self, node1: GraphNode, node2: GraphNode) -> None:
        """Union the sets containing node1 and node2 using union by rank."""

        root1 = self.find_root(node1)
        root2 = self.find_root(node2)

        if root1 == root2:
            # Cycle detected
            return False

        # Union by rank
        # Attach smaller rank tree under root of
        # high rank tree (Union by Rank)
        if self.rank[root1] < self.rank[root2]:
            self.parent[root1] = root2
        elif self.rank[root1] > self.rank[root2]:
            self.parent[root2] = root1
        # If ranks are same, then mark first one as root
        # and increment its rank by one
        else:
            self.parent[root2] = root1
            self.rank[root1] += 1

        return True


def convert_to_directed_tree(graph: Graph, root_node: GraphNode | None = None) -> Graph:
    """Converts an undirected graph to a directed graph.

    If root_node is provided, the directed graph will start from that node.
    Otherwise, it will attempt to select as root_node the first node it finds with a single neighbor.

    Args:
        graph: Undirected graph.
        root_node: Optional starting node for directed graph.

    Returns:
        Directed graph.
    """
    if root_node is None:
        # Find root(s)
        root_nodes = [
            node for node in graph.get_nodes() if len(graph.get_neighbors(node)) == 1
        ]
        if not root_nodes:
            raise RuntimeError(f"{MACRO_NAME}: Could not find root node for assembly")

        # Select first one as main root node
        root_node = root_nodes[0]
    else:
        if root_node not in graph.get_nodes():
            raise RuntimeError(
                f"{MACRO_NAME}: Provided root_node, {root_node.part.Name}, is not part of graph"
            )

    visited: set[GraphNode] = set()
    directed_tree = Graph(is_directed=True)

    def dfs(node: GraphNode) -> None:
        visited.add(node)
        for neighbor in graph.get_neighbors(node):
            if neighbor not in visited:
                # Get edge from undirected graph
                edge = graph.get_edge(node, neighbor)
                # Add only one direction
                directed_tree.add_edge(node.part, neighbor.part, edge.joint)
                dfs(neighbor)

    dfs(root_node)
    return directed_tree


def find_minimum_spanning_tree(
    graph: Graph,
) -> tuple[Graph, list[tuple[GraphNode, GraphNode, GraphEdge]]]:
    """Builds minimum spanning tree using Kruskal's algorithm.

    Returns:
        tree_edges: List of edges representing the minimum spanning tree.
        unused_edges: List of unused edges that would form loops.
    """
    uf = UnionFind(graph)

    # sort edges in non-decreasing order of weights
    sorted_edges = sorted(graph.get_edges(), key=lambda e: e[2].weight)

    # Track which edges are used in the tree
    # and which ones are not
    tree = Graph()
    unused_edges: list[tuple[GraphNode, GraphNode, GraphEdge]] = []
    for u, v, edge in sorted_edges:
        if uf.union(u, v):
            tree.add_edge(u.part, v.part, edge.joint)
        else:
            unused_edges.append((u, v, edge))

    return tree, unused_edges


####################################################################
# MuJuCo Exporter Class
####################################################################


class MuJuCoExporter:
    """Class for exporting a kinematic tree as a MuJoCo MJCF (XML) file and STL files.

    Args:
        integrator: The numerical integrator to be used in MuJoCo.
            The available integrators are the semi-implicit Euler method,
            the fixed-step 4-th order Runge Kutta method,
            the Implicit-in-velocity Euler method, and implicitfast.
        timestep: Simulation time step in seconds.
    """

    def __init__(
        self,
        linear_deflection: float = DEFAULT_LINEAR_DEFLECTION,
        angular_deflection: float = DEFAULT_ANGULAR_DEFLECTION,
        integrator: Literal[
            "Euler", "implicit", "implicitfast", "RK4"
        ] = DEFAULT_MJCF_INTEGRATOR,
        timestep: float = DEFAULT_MJCF_TIMESTEP,
        solver: Literal["PGS", "CG", "Newton"] = DEFAULT_MJCF_SOLVER,
    ) -> None:
        self.linear_deflection = linear_deflection
        self.angular_deflection = angular_deflection
        self.integrator = integrator
        self.timestep = timestep
        self.solver = solver

        self.mujoco = ET.Element("mujoco")
        self.option = ET.SubElement(
            self.mujoco,
            "option",
            integrator=self.integrator,
            timestep=str(self.timestep),
            solver=self.solver,
        )
        self.compiler = ET.SubElement(
            self.mujoco,
            "compiler",
            meshdir="meshes",
            autolimits="true",
            inertiafromgeom="true",
            angle="radian",
        )
        # Add defaults
        self.default = ET.SubElement(self.mujoco, "default")
        ET.SubElement(
            self.default,
            "joint",
            damping="10.0",
            armature="1.0",
        )
        ET.SubElement(
            self.default,
            "geom",
            conaffinity="0",
            condim="3",
            friction="1 0.5 0.5",
            margin="0",
        )
        # Add assets
        self.asset = ET.SubElement(self.mujoco, "asset")
        ET.SubElement(
            self.asset,
            "texture",
            type="skybox",
            builtin="gradient",
            rgb1="0.3 0.5 0.7",
            rgb2="0 0 0",
            width="512",
            height="3072",
        )
        ET.SubElement(
            self.asset,
            "texture",
            type="2d",
            name="groundplane",
            builtin="checker",
            mark="edge",
            rgb1="0.2 0.3 0.4",
            rgb2="0.1 0.2 0.3",
            markrgb="0.8 0.8 0.8",
            width="300",
            height="300",
        )
        ET.SubElement(
            self.asset,
            "material",
            name="groundplane",
            texture="groundplane",
            texuniform="true",
            texrepeat="5 5",
            reflectance="0.1",
        )

        self.worldbody = ET.SubElement(self.mujoco, "worldbody")
        # Add multiple light sources for better visualization
        self.worldbody.append(ET.Comment("Lighting and floor"))
        ET.SubElement(
            self.worldbody, "light", diffuse=".8 .8 .8", pos="0 0 4", dir="0 0 -1"
        )
        ET.SubElement(
            self.worldbody, "light", diffuse=".6 .6 .6", pos="4 4 4", dir="-1 -1 -1"
        )
        # Placeholder for elements that will be added when exporting
        self.contact = ET.SubElement(self.mujoco, "contact")
        self.equality = ET.SubElement(self.mujoco, "equality")
        self.tendon = ET.SubElement(self.mujoco, "tendon")
        self.actuator = ET.SubElement(self.mujoco, "actuator")
        self.sensor = ET.SubElement(self.mujoco, "sensor")

    def export_assembly(
        self, assembly: App.DocumentObject, output_dir: str | os.PathLike
    ) -> None:
        """Main export method"""

        # Create graph connecting parts with joints
        assembly_graph = Graph.from_assembly(assembly)

        # Export assembly parts as binary stl meshes
        meshes_dir = Path(output_dir).joinpath("meshes")
        meshes_dir.mkdir(exist_ok=True, parents=True)
        self.worldbody.append(ET.Comment("Part Meshes"))
        self.export_parts_as_meshes_and_add_to_assets(assembly_graph, meshes_dir)

        # Add floorplane (cosmetic)
        self.add_floorplane(assembly_graph)
        self.worldbody.append(ET.Comment("Assembly"))

        # Find minimum spanning tree representing kinematic tree
        # As well as unused edges (joints) that will be converted to equality constraints
        tree, unused_edges = find_minimum_spanning_tree(assembly_graph)

        # Use grounded part as root node
        root_node: GraphNode | None = None
        grounded_joints = [
            joint
            for joint in UtilsAssembly.getJointGroup(assembly).Group
            if hasattr(joint, "ObjectToGround")
        ]
        if grounded_joints:
            grounded_joint = grounded_joints[0]
            grounded_part = grounded_joint.ObjectToGround
            # Find corresponding node
            root_node = [
                node for node in tree.get_nodes() if node.part == grounded_part
            ][0]

        # Build tree
        tree = convert_to_directed_tree(tree, root_node)
        if root_node is None:
            root_node = tree.get_nodes()[0]
        self.process_tree(root_node, tree)

        # Handle kinematic loops
        if unused_edges:
            self.process_kinematic_loops(unused_edges)

        # Save MJCF file
        xml_file = (
            Path(output_dir).joinpath(App.activeDocument().Name).with_suffix(".xml")
        )
        self.write_xml(xml_file)

    def export_parts_as_meshes_and_add_to_assets(
        self,
        assembly_graph: Graph,
        meshes_dir: str | os.PathLike,
    ) -> None:
        for node in assembly_graph.get_nodes():
            part = node.part
            shape = part.Shape.copy(False)

            log_message(f"Shape: Name={part.Name}, Placement={shape.Placement}")

            mesh = MeshPart.meshFromShape(
                Shape=shape,
                LinearDeflection=self.linear_deflection,
                AngularDeflection=self.angular_deflection,
                Relative=False,
            )
            mesh_file = Path(meshes_dir).joinpath(part.Name).with_suffix(".stl")
            mesh.write(os.fspath(mesh_file))
            # Add new mesh to assets
            ET.SubElement(
                self.asset,
                "mesh",
                name=part.Name,
                file=mesh_file.name,
                # Convert mm to m
                scale="0.001 0.001 0.001",
            )
            # Add material for appearance to assets
            appearance_dict = node.get_body_appearance()
            found_existing_materials = self.asset.findall(
                f"./material[@name='{appearance_dict['name']}']"
            )
            # Add material only if it wasn't added already
            # We do the check by name
            # TODO: Consider using a dictionary to keep track of added materials
            if len(found_existing_materials) == 0:
                ET.SubElement(self.asset, "material", **appearance_dict)

    def add_floorplane(self, assembly_graph: Graph) -> None:
        minimum_z_placement: float | None = None
        for node in assembly_graph.get_nodes():
            part = node.part
            if minimum_z_placement is None:
                minimum_z_placement = part.Placement.Base[2]
            else:
                minimum_z_placement = min(minimum_z_placement, part.Placement.Base[2])
        if minimum_z_placement is None:
            raise RuntimeError(f"{MACRO_NAME}: This should not happen")
        # convert from mm to m
        minimum_z_placement *= 0.001
        # shift placement to account for floorplane size
        floor_z_pos = minimum_z_placement - 0.001
        # Add floorplane under lowest part
        ET.SubElement(
            self.worldbody,
            "geom",
            name="floor",
            pos=f"0 0 {floor_z_pos}",
            size="0 0 1",
            type="plane",
            material="groundplane",
        )

    def process_tree(
        self,
        current_node: GraphNode,
        tree: Graph,
        *,
        parent_node: ET.Element | None = None,
        body_elements: dict[GraphNode, ET.Element] | None = None,
    ) -> ET.Element:
        if body_elements is None:
            body_elements = {}
        parent_body = body_elements.get(parent_node, self.worldbody)

        if (current_body := body_elements.get(current_node)) is None:
            current_body = self.add_body(current_node, parent_body)
            body_elements[current_node] = current_body

        for child_node in tree.get_neighbors(current_node):
            child_body = self.process_tree(
                child_node,
                tree,
                parent_node=current_node,
                body_elements=body_elements,
            )
            edge = tree.get_edge(current_node, child_node)
            self.add_joint_to_body(child_body, edge)
        return current_body

    def add_body(self, node: GraphNode, parent_body: ET.Element) -> ET.Element:
        # Create body element for this part
        pos, quat = node.get_body_position_and_orientation()
        body = ET.SubElement(
            parent_body,
            "body",
            name=node.part.Name,
            pos=pos,
            quat=quat,
        )
        # Add mesh for visualization
        appearance_dict = node.get_body_appearance()
        ET.SubElement(
            body,
            "geom",
            type="mesh",
            name=f"{node.part.Name} geom",
            mesh=node.part.Name,
            material=appearance_dict["name"],
            contype="0",
            conaffinity="0",
        )
        return body

    def add_joint_to_body(
        self,
        body: ET.Element,
        edge: GraphEdge,
    ) -> ET.Element:
        """Add a joint to a body element"""
        joint_type = edge.get_mujoco_joint_type()

        if joint_type is None or joint_type == "fixed":
            return None

        joint_pos, joint_axis = edge.get_joint_position_and_axis()
        joint_range = edge.get_joint_range()

        # Create the joint element
        joint_element = ET.SubElement(
            body,
            "joint",
            type=joint_type,
            name=edge.joint.Label,
            pos=joint_pos,
            axis=joint_axis,
        )
        if joint_range is not None:
            joint_element.set("range", joint_range)

        # Create actuator element
        actuator_element = ET.SubElement(
            self.actuator,
            "position",
            name=joint_element.get("name"),
            joint=joint_element.get("name"),
            kp="100",
        )
        if joint_range is not None:
            actuator_element.set("ctrlrange", joint_range)

        # Create sensor element
        ET.SubElement(
            self.sensor,
            "jointpos",
            name=joint_element.get("name") + "_pos",
            joint=joint_element.get("name"),
        )
        return joint_element

    def process_kinematic_loops(
        self, unused_edges: list[tuple[GraphNode, GraphNode, GraphEdge]]
    ) -> None:
        log_message(f"Found {len(unused_edges)} kinematic loops in the assembly")
        for u, v, edge in unused_edges:
            joint_type = edge.get_mujoco_joint_type()
            if joint_type is None:
                # For fixed joints, use weld constraint
                ET.SubElement(
                    self.equality,
                    "weld",
                    name=f"loop_weld_{edge.joint.Label}",
                    body1=u.part.Name,
                    body2=v.part.Name,
                    solref="0.01 1",
                    solimp="0.9 0.95 0.001",
                )
            else:
                raise NotImplementedError(
                    f"Processing kinematic loop not implemented for joint type '{joint_type}'"
                )

    def write_xml(self, xml_file: str | os.PathLike) -> None:
        """Writes final XML structure to a file.

        Args:
            xml_file: Output path to XML file.
        """
        ET.indent(self.mujoco)
        tree = ET.ElementTree(self.mujoco)
        tree.write(xml_file, encoding="utf-8", xml_declaration=True)
        log_message(f"Successfully exported to {xml_file}")


####################################################################
# Export Dialog
####################################################################


class ExportTaskPanel:
    def __init__(self):
        # Get current document and its path
        self.doc = App.ActiveDocument
        if not self.doc:
            log_message("No active document", level="error")
            raise RuntimeError("No active document")

        self.default_dir = Path(".")
        if self.doc.FileName:
            self.default_dir = Path(self.doc.FileName).parent / "mujoco"

        self.setup_ui()

    def setup_ui(self) -> None:
        # Create the form widget
        self.form = QtWidgets.QWidget()
        self.form.setWindowTitle("Export FreeCAD Assembly to MuJoCo")

        # Create main layout
        main_layout = QtWidgets.QVBoxLayout(self.form)

        # Directory selection section
        dir_group = QtWidgets.QGroupBox("Export Directory")
        dir_layout = QtWidgets.QHBoxLayout()

        self.dir_edit = QtWidgets.QLineEdit(os.fspath(self.default_dir))
        dir_layout.addWidget(self.dir_edit)

        browse_button = QtWidgets.QPushButton("Browse...")
        browse_button.clicked.connect(self.browse_export_directory)
        dir_layout.addWidget(browse_button)

        dir_group.setLayout(dir_layout)
        main_layout.addWidget(dir_group)

        # STL Export options
        stl_group = QtWidgets.QGroupBox("STL Export Options")
        stl_layout = QtWidgets.QFormLayout()

        ## Mesh quality
        self.linear_deflection_spin = QtWidgets.QDoubleSpinBox()
        self.linear_deflection_spin.setRange(0.01, 1)
        self.linear_deflection_spin.setSingleStep(0.01)
        self.linear_deflection_spin.setDecimals(2)
        self.linear_deflection_spin.setValue(DEFAULT_LINEAR_DEFLECTION)
        stl_layout.addRow("Linear Deflection:", self.linear_deflection_spin)

        self.angular_deflection_spin = QtWidgets.QDoubleSpinBox()
        self.angular_deflection_spin.setRange(0.5, 5.0)
        self.angular_deflection_spin.setSingleStep(0.1)
        self.angular_deflection_spin.setDecimals(1)
        self.angular_deflection_spin.setValue(DEFAULT_ANGULAR_DEFLECTION)
        stl_layout.addRow("Angular Deflection:", self.angular_deflection_spin)

        stl_group.setLayout(stl_layout)
        main_layout.addWidget(stl_group)

        # MuJoCo MJCF parameters
        mjcf_group = QtWidgets.QGroupBox("MuJoCo MJCF Parameters")
        mjcf_layout = QtWidgets.QFormLayout()

        ## Timestep
        self.timestep_spin = QtWidgets.QDoubleSpinBox()
        self.timestep_spin.setRange(0.0001, 0.05)
        self.timestep_spin.setSingleStep(0.0001)
        self.timestep_spin.setDecimals(4)
        self.timestep_spin.setValue(DEFAULT_MJCF_TIMESTEP)
        mjcf_layout.addRow("Timestep:", self.timestep_spin)

        ## Damping
        self.damping_spin = QtWidgets.QDoubleSpinBox()
        self.damping_spin.setRange(0.0, 10.0)
        self.damping_spin.setSingleStep(0.1)
        self.damping_spin.setDecimals(3)
        self.damping_spin.setValue(DEFAULT_MJCF_DAMPING)
        mjcf_layout.addRow("Default Damping:", self.damping_spin)

        ## Armature
        self.armature_spin = QtWidgets.QDoubleSpinBox()
        self.armature_spin.setRange(0.0, 1.0)
        self.armature_spin.setSingleStep(0.01)
        self.armature_spin.setDecimals(3)
        self.armature_spin.setValue(DEFAULT_MJCF_ARMATURE)
        mjcf_layout.addRow("Default Armature:", self.armature_spin)

        # Additional common parameters
        self.integrator_combo = QtWidgets.QComboBox()
        integrator_values = ["implicitfast", "Euler", "implicit", "RK4"]
        integrator_values = [DEFAULT_MJCF_INTEGRATOR] + list(
            set(integrator_values).difference([DEFAULT_MJCF_INTEGRATOR])
        )
        self.integrator_combo.addItems(integrator_values)
        mjcf_layout.addRow("Integrator:", self.integrator_combo)

        self.solver_combo = QtWidgets.QComboBox()
        solver_values = ["PGS", "CG", "Newton"]
        solver_values = [DEFAULT_MJCF_SOLVER] + list(
            set(solver_values).difference([DEFAULT_MJCF_SOLVER])
        )
        self.solver_combo.addItems(solver_values)
        mjcf_layout.addRow("Solver:", self.solver_combo)

        mjcf_group.setLayout(mjcf_layout)
        main_layout.addWidget(mjcf_group)

        # Debug
        debug_group = QtWidgets.QGroupBox("Debug Options")
        debug_layout = QtWidgets.QVBoxLayout()

        clear_report_button = QtWidgets.QPushButton("Clear Report View")
        clear_report_button.clicked.connect(self.clear_report_view)
        debug_layout.addWidget(clear_report_button)

        debug_group.setLayout(debug_layout)
        main_layout.addWidget(debug_group)

    def browse_export_directory(self) -> None:
        directory = QtWidgets.QFileDialog.getExistingDirectory(
            self.form, "Select Export Directory", self.dir_edit.text()
        )
        if directory:
            self.dir_edit.setText(directory)

    def clear_report_view(self) -> None:
        """Clear the contents of the FreeCAD Report View"""
        main_window = Gui.getMainWindow()
        if not main_window:
            log_message("Cannot find main window to clear report view", level="warning")
            return

        try:
            r = main_window.findChild(QtGui.QTextEdit, "Report view")
            r.clear()
            return
        except Exception as e:
            log_message(
                f"Error while trying to clear Report view: {str(e)}", level="error"
            )

    def accept(self) -> bool:
        """Called when user clicks the export button in the task panel

        Returns:
            True, if the task panel should be closed. False otherwise.
        """
        # Get all parameters from UI
        export_dir = Path(self.dir_edit.text())
        export_dir.mkdir(exist_ok=True)

        # Validate export directory
        if not os.path.isdir(export_dir):
            QtWidgets.QMessageBox.warning(
                self.form,
                "Directory Error",
                f"The directory '{export_dir}' does not exist. Please select a valid directory.",
            )
            return False

        # Collect parameters
        export_params = {
            "linear_deflection": self.linear_deflection_spin.value(),
            "angular_deflection": self.angular_deflection_spin.value(),
            "mjcf_timestep": self.timestep_spin.value(),
            "mjcf_damping": self.damping_spin.value(),
            "mjcf_armature": self.armature_spin.value(),
            "mjcf_integrator": self.integrator_combo.currentText(),
            "mjcf_solver": self.solver_combo.currentText(),
        }

        selection = Gui.Selection.getSelectionEx()
        if not selection:
            log_message("Please select an assembly", level="error")
            QtWidgets.QMessageBox.warning(
                self.form,
                f"{MACRO_NAME}",
                "Please select an assembly.",
            )
            return False

        if len(selection) != 1:
            log_message(
                f"Expected selection to contain 1 object instead of {len(selection)}. Please only select an assembly",
                level="error",
            )
            QtWidgets.QMessageBox.warning(
                self.form,
                f"{MACRO_NAME}",
                f"Expected selection to contain 1 object instead of {len(selection)}. Please only select an assembly.",
            )
            return False

        if selection[0].Object.Type != "Assembly":
            log_message(
                f"Expected selection to be an object of type Assembly instead of {selection[0].Object.Type}",
                level="error",
            )
            QtWidgets.QMessageBox.warning(
                self.form,
                f"{MACRO_NAME}",
                f"Expected selection to be an object of type Assembly instead of {selection[0].Object.Type}",
            )
            return False

        assembly = selection[0].Object

        try:
            # Export to MuJoCo Format
            exporter = MuJuCoExporter(
                integrator=export_params["mjcf_integrator"],
                timestep=export_params["mjcf_timestep"],
            )
            exporter.export_assembly(assembly, output_dir=export_dir)

            # Success message
            QtWidgets.QMessageBox.information(
                self.form,
                "Export Successful",
                f"Files have been exported to:\n{export_dir}",
            )

            return True

        except Exception as e:
            QtWidgets.QMessageBox.critical(
                self.form, "Export Error", f"An error occurred during export:\n{str(e)}"
            )
            return False


####################################################################
# Macro Entrypoint
####################################################################

if __name__ == "__main__":
    panel = ExportTaskPanel()
    Gui.Control.showDialog(panel)
